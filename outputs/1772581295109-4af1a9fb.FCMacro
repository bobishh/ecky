import math
import FreeCAD as App
import Part

# ---------------- USER PARAMETERS ----------------
INNER_HEIGHT = 80.0
INNER_BOTTOM_DIAMETER = 72.0
INNER_TOP_DIAMETER = 100.0
RADIAL_CLEARANCE = 0.8
WALL_THICKNESS = 1.6
BOTTOM_THICKNESS = 1.2

# Shape controls (small, user-tunable set)
BELLY_AMOUNT_MM = 5.0          # outward bulge at mid-height (0..12 recommended)
FANCINESS_INTENSITY = 0.85     # 0.0..1.5
PATTERN_DENSITY = 1.0          # 0.5..2.0
# -------------------------------------------------


def clamp(v, lo, hi):
    return max(lo, min(hi, float(v)))


BELLY_AMOUNT_MM = clamp(BELLY_AMOUNT_MM, 0.0, 12.0)
FANCINESS_INTENSITY = clamp(FANCINESS_INTENSITY, 0.0, 1.5)
PATTERN_DENSITY = clamp(PATTERN_DENSITY, 0.5, 2.0)

inner_bottom_r = INNER_BOTTOM_DIAMETER * 0.5 + RADIAL_CLEARANCE
inner_top_r = INNER_TOP_DIAMETER * 0.5 + RADIAL_CLEARANCE


def radius_at_u(u):
    base = inner_bottom_r + (inner_top_r - inner_bottom_r) * u
    # Smooth "belly" keeps top and bottom radii exact, adds non-conical silhouette.
    belly = BELLY_AMOUNT_MM * (math.sin(math.pi * u) ** 2)
    return base + belly


def make_inner_cavity_solid():
    section_count = int(24 + 20 * PATTERN_DENSITY)
    wires = []
    for i in range(section_count + 1):
        u = i / float(section_count)
        z = INNER_HEIGHT * u
        r = radius_at_u(u)
        c = Part.makeCircle(r, App.Vector(0, 0, z), App.Vector(0, 0, 1))
        wires.append(Part.Wire([c]))

    loft = Part.makeLoft(wires, True, False, False)
    if loft.ShapeType != "Solid":
        loft = Part.Solid(loft)
    return loft


def make_offset_solid(shape, offset_mm):
    attempts = [
        lambda: shape.makeOffsetShape(offset_mm, 0.05, False, False, 0, 2, True),
        lambda: shape.makeOffsetShape(offset_mm, 0.05, False, False, 0, 1, True),
        lambda: shape.makeOffsetShape(offset_mm, 0.05, join=2, fill=True),
        lambda: shape.makeOffsetShape(offset_mm, 0.05),
    ]
    for fn in attempts:
        try:
            out = fn()
            if out and not out.isNull():
                return out
        except Exception:
            pass
    raise RuntimeError("Offset operation failed for all signatures.")


def open_top_and_set_bottom_thickness(shell_shape):
    span_r = max(inner_bottom_r, inner_top_r) + BELLY_AMOUNT_MM + WALL_THICKNESS + 30.0
    span = span_r * 2.0

    # Remove any top cap generated by offsetting a closed inner solid.
    top_cut = Part.makeBox(
        span,
        span,
        INNER_HEIGHT + 30.0,
        App.Vector(-span_r, -span_r, INNER_HEIGHT - 0.05),
    )
    opened = shell_shape.cut(top_cut)

    # Offset usually extends below z=0 by ~WALL_THICKNESS. Keep only z >= -BOTTOM_THICKNESS.
    keep = Part.makeBox(
        span,
        span,
        INNER_HEIGHT + BOTTOM_THICKNESS + 40.0,
        App.Vector(-span_r, -span_r, -BOTTOM_THICKNESS),
    )
    trimmed = opened.common(keep)

    # Move so outer base sits at z=0; inner cavity floor lands at z=BOTTOM_THICKNESS.
    return trimmed.translated(App.Vector(0, 0, BOTTOM_THICKNESS))


def make_base_pot():
    inner = make_inner_cavity_solid()
    outer = make_offset_solid(inner, WALL_THICKNESS)
    shell = outer.cut(inner)
    pot = open_top_and_set_bottom_thickness(shell)
    if pot.isNull() or pot.Volume <= 0:
        raise RuntimeError("Base pot shape is invalid.")
    return pot


def make_fancy_cutters():
    if FANCINESS_INTENSITY <= 1e-6:
        return None

    rows = int(20 + 18 * PATTERN_DENSITY)
    strands = int(4 + round(4 * PATTERN_DENSITY))
    groove_r = 0.55 + 0.65 * FANCINESS_INTENSITY
    twist_turns = 0.8 + 1.8 * PATTERN_DENSITY

    cutters = []
    for j in range(rows):
        u = (j + 0.5) / float(rows)
        z = BOTTOM_THICKNESS + INNER_HEIGHT * (0.03 + 0.94 * u)

        r_outer_nominal = radius_at_u(u) + WALL_THICKNESS
        center_r = r_outer_nominal + groove_r * 0.45

        for k in range(strands):
            theta = (2.0 * math.pi * k / float(strands)) + (2.0 * math.pi * twist_turns * u)
            cx = center_r * math.cos(theta)
            cy = center_r * math.sin(theta)
            cutters.append(Part.makeSphere(groove_r, App.Vector(cx, cy, z)))

    if not cutters:
        return None
    return Part.makeCompound(cutters)


if App.ActiveDocument is None:
    doc = App.newDocument("CachePotDoc")
else:
    doc = App.ActiveDocument

base_shape = make_base_pot()
base_obj = doc.addObject("Part::Feature", "CachePot")
base_obj.Shape = base_shape

try:
    cutter_compound = make_fancy_cutters()
    if cutter_compound is not None:
        fancy_shape = base_shape.cut(cutter_compound)
        if fancy_shape and not fancy_shape.isNull() and fancy_shape.Volume > 0:
            fancy_obj = doc.addObject("Part::Feature", "CachePotFancy")
            fancy_obj.Shape = fancy_shape
except Exception as exc:
    App.Console.PrintWarning("Fancy decoration failed; keeping base pot only: {}\n".format(exc))

doc.recompute()

try:
    import FreeCADGui as Gui
    Gui.ActiveDocument.ActiveView.fitAll()
except Exception:
    pass
